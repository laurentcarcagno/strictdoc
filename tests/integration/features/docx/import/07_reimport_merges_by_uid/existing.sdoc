[DOCUMENT]
TITLE: input

[GRAMMAR]
ELEMENTS:
- TAG: SECTION
  PROPERTIES:
    IS_COMPOSITE: True
  FIELDS:
  - TITLE: UID
    TYPE: String
    REQUIRED: False
  - TITLE: LEVEL
    TYPE: String
    REQUIRED: False
  - TITLE: PREFIX
    TYPE: String
    REQUIRED: False
  - TITLE: TITLE
    TYPE: String
    REQUIRED: True
- TAG: TEXT
  FIELDS:
  - TITLE: STATEMENT
    TYPE: String
    REQUIRED: True
- TAG: REQUIREMENT
  FIELDS:
  - TITLE: UID
    TYPE: String
    REQUIRED: False
  - TITLE: VERSION
    TYPE: String
    REQUIRED: False
  - TITLE: VERIFIED_BY
    TYPE: String
    REQUIRED: False
  - TITLE: LINKED_REQ
    TYPE: String
    REQUIRED: False
  - TITLE: TITLE
    TYPE: String
    REQUIRED: True
  - TITLE: STATEMENT
    TYPE: String
    REQUIRED: True
  - TITLE: NOTE
    TYPE: String
    REQUIRED: False
  - TITLE: OWNER
    TYPE: String
    REQUIRED: False
  RELATIONS:
  - TYPE: Parent
  - TYPE: File

[[SECTION]]
TITLE: Requirements

[REQUIREMENT]
UID: SYS-0001
VERSION: V1
VERIFIED_BY: T
TITLE: Power on
STATEMENT: >>>
The system shall power on.
<<<
OWNER: Alice
RELATIONS:
- TYPE: File
  VALUE: src/power.c

[REQUIREMENT]
UID: SYS-0002
VERSION: V0
VERIFIED_BY: T
TITLE: Power off
STATEMENT: >>>
The system shall power off.
<<<
OWNER: Bob

[[/SECTION]]
