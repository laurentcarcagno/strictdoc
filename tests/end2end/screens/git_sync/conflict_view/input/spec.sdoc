[DOCUMENT]
TITLE: Spec
OPTIONS:
  ENABLE_MID: True

[REQUIREMENT]
MID: 11111111111111111111111111111111
UID: R-1
TITLE: Start
STATEMENT: >>>
The engine shall start.
<<<

[REQUIREMENT]
MID: 22222222222222222222222222222222
UID: R-2
TITLE: Stop
STATEMENT: >>>
The engine shall stop.
<<<
