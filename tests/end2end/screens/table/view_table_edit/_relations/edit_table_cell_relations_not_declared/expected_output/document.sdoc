[DOCUMENT]
TITLE: Document

[GRAMMAR]
ELEMENTS:
- TAG: NOTE
  FIELDS:
  - TITLE: TITLE
    TYPE: String
    REQUIRED: True
- TAG: REQUIREMENT
  FIELDS:
  - TITLE: UID
    TYPE: String
    REQUIRED: True
  - TITLE: TITLE
    TYPE: String
    REQUIRED: True
  RELATIONS:
  - TYPE: Parent

[NOTE]
TITLE: Note title

[REQUIREMENT]
UID: REQ-001
TITLE: Requirement title
