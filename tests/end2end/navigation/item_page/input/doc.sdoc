[DOCUMENT]
TITLE: Item page

[REQUIREMENT]
UID: REQ-1
TITLE: Parent
STATEMENT: Parent statement.

[REQUIREMENT]
UID: REQ-2
TITLE: Child
STATEMENT: Child statement.
RELATIONS:
- TYPE: Parent
  VALUE: REQ-1
